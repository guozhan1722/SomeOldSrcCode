Microhard-MIB DEFINITIONS ::= BEGIN

-- Title:	MICROHARD MIB
-- Date:	Sep 10, 2010
-- Disription: Not all parameters are supported in a paticular device,Support of parameters varies 
-- from version to version

IMPORTS
        MODULE-IDENTITY,
        OBJECT-IDENTITY,
        enterprises,
        OBJECT-TYPE, 
        NetworkAddress, 
        IpAddress,
        Counter, 
        Gauge, 
        TimeTicks
	FROM RFC1065-SMI;
--	DisplayString
--		FROM RFC1158-MIB;

Microhard OBJECT IDENTIFIER ::=	{ enterprises 21703 }

--VIP4G
	VIP4G				OBJECT IDENTIFIER ::=	{ Microhard 6000 }
	SystemConfig			OBJECT IDENTIFIER ::=	{ VIP4G 1 }
	NetworkConfig			OBJECT IDENTIFIER ::=	{ VIP4G 2 }
	Carrier				OBJECT IDENTIFIER ::=	{ IP3G 3 }
	WirelessConfig			OBJECT IDENTIFIER ::=	{ VIP4G 4 }
	COM1Config			OBJECT IDENTIFIER ::=	{ VIP4G 4 }
	COM2Config			OBJECT IDENTIFIER ::=	{ VIP4G 5 }
	SecurityConfig			OBJECT IDENTIFIER ::=	{ VIP4G 6 }
	SystemInformation		OBJECT IDENTIFIER ::=	{ VIP4G 7 }
	SystemTools			OBJECT IDENTIFIER ::=	{ VIP4G 8 }
	Misc				OBJECT IDENTIFIER ::=	{ VIP4G 9 }

-- SystemConfig parameter group

	System_Host_Name	OBJECT-TYPE
		SYNTAX	DisplayString (SIZE (0..32))
		ACCESS	read-write
		STATUS	mandatory
		DESCRIPTION "System"
		::= { SystemConfig 1}


	System_Date_Mode	OBJECT-TYPE
		SYNTAX	INTEGER {
		local(0),
		sync(1)		
		} 
		ACCESS	read-write
		STATUS	mandatory
		DESCRIPTION ""
		::= { SystemConfig 2 }


	System_HTTP_Port	OBJECT-TYPE
		SYNTAX	DisplayString (SIZE (0..32))
		ACCESS	read-write
		STATUS	mandatory
		DESCRIPTION "System"
		::= { SystemConfig 10}


	System_HTTP_SSL_MODE	OBJECT-TYPE
		SYNTAX	INTEGER {
		disable(0),
		enable(1)		
		} 
		ACCESS	read-write
		STATUS	mandatory
		DESCRIPTION ""
		::= { SystemConfig 11 }

	
	SystemConfigAction	OBJECT-TYPE
		SYNTAX	INTEGER {
		SubmitOrReset(0),
		Submit(1),
		Reset(2)
		} 
		ACCESS	read-write
		STATUS	mandatory
		DESCRIPTION "0-Default no selection.1-Submit,this will update setting immidiately.
		2-Reset,this will cacel all related settings in the sub tree" 
		::= { SystemConfig 15 }


-- Network parameter group

	IPConfig	OBJECT IDENTIFIER ::=	{ NetworkConfig 1 }
		-- IPConfig parameter group

	IPAddressMode	OBJECT-TYPE
		SYNTAX	INTEGER {
		static(0),
		dhcp(1)		
		} 
		ACCESS	read-write
		STATUS	mandatory
		DESCRIPTION "IP Address Mode: 0 - static 1 - dhcp"
		::= { IPConfig 1 }

	IPAddress	OBJECT-TYPE
		SYNTAX	DisplayString (SIZE (0..32))
		ACCESS	read-write
		STATUS	mandatory
		DESCRIPTION "IP Address."
		::= { IPConfig 2 }

	IPSubNetMask	OBJECT-TYPE
		SYNTAX	DisplayString (SIZE (0..32))
		ACCESS	read-write
		STATUS	mandatory
		DESCRIPTION "IP SubNet Mask."
		::= { IPConfig 3 }

	IPGateWay	OBJECT-TYPE
		SYNTAX	DisplayString (SIZE (0..32))
		ACCESS	read-write
		STATUS	mandatory
		 DESCRIPTION "IP Gate Way."
		::= { IPConfig 4 }
		
	IPDNS		OBJECT-TYPE
		SYNTAX	DisplayString (SIZE (0..32))
		ACCESS	read-write
		STATUS	mandatory
		DESCRIPTION "IP DNS ADDRESS."
		::= { IPConfig 5 }

	IPConfigAction	OBJECT-TYPE
		SYNTAX	INTEGER {
		SubmitOrReset(0),
		Submit(1),
		Reset(2)
		} 
		ACCESS	read-write
		STATUS	mandatory
		DESCRIPTION "0-Default no selection.1-Submit,this will update setting immidiately.
		2-Reset,this will cacel all related settings in the sub tree" 
		::= { IPConfig 9 }

	NTPConfig	OBJECT IDENTIFIER ::=	{ NetworkConfig 2 }
		-- NTPConfig parameter group

	NTPServerName	OBJECT-TYPE
		SYNTAX	DisplayString (SIZE (0..32))
		ACCESS	read-write
		STATUS	mandatory
		DESCRIPTION "NTP Server Name."
		::= { NTPConfig 1 }

	NTPServerPort	OBJECT-TYPE
		SYNTAX	DisplayString (SIZE (0..32))
		ACCESS	read-write
		STATUS	mandatory
		DESCRIPTION "NTP Server Port."
		::= { NTPConfig 2 }

	NTPConfigAction	OBJECT-TYPE
		SYNTAX	INTEGER {
		SubmitOrReset(0),
		Submit(1),
		Reset(2)
		} 
		ACCESS	read-write
		STATUS	mandatory
		DESCRIPTION "0-Default no selection.1-Submit,this will update setting immidiately.
		2-Reset,this will cacel all related settings in the sub tree" 
		::= { NTPConfig 3 }

	DHCPConfig	OBJECT IDENTIFIER ::=	{ NetworkConfig 3 }
		-- DHCPConfig parameter group

	DHCPServerStatus	OBJECT-TYPE
		SYNTAX	INTEGER {
		Enable(0),
		Disable(1)
		} 
		ACCESS	read-write
		STATUS	mandatory
		DESCRIPTION "NTP Server Status:  0 - Enable 1 - Disable."
		::= { DHCPConfig 1 }

	DHCPStartAddress	OBJECT-TYPE
		SYNTAX	DisplayString (SIZE (0..32))
		ACCESS	read-write
		STATUS	mandatory
		DESCRIPTION "DHCP Start Address."
		::= {DHCPConfig 4 }
		
	DHCPAddressLimit	OBJECT-TYPE
		SYNTAX	DisplayString (SIZE (0..32))
		ACCESS	read-write
		STATUS	mandatory
		DESCRIPTION "DHCP Server Address Limit."
		::= { DHCPConfig 5 }

	DHCPLeaseTime		OBJECT-TYPE
		SYNTAX	DisplayString (SIZE (0..32))
		ACCESS	read-write
		STATUS	mandatory
		DESCRIPTION "DHCP Server Lease Time."
		::= { DHCPConfig 6 }

	DHCPConfigAction	OBJECT-TYPE
		SYNTAX	INTEGER {
		SubmitOrReset(0),
		Submit(1),
		Reset(2)
		} 
		ACCESS	read-write
		STATUS	mandatory
		DESCRIPTION "0-Default no selection.1-Submit,this will update setting immidiately.
		2-Reset,this will cacel all related settings in the sub tree" 
		::= {DHCPConfig 24 }


	SNMPConfig	OBJECT IDENTIFIER ::=	{ NetworkConfig 4 }
		-- SNMPConfig parameter group

	SNMPMode	OBJECT-TYPE
		SYNTAX	INTEGER {
		Disable(0),
		Enable(1)
		} 
		ACCESS	read-write
		STATUS	mandatory
		DESCRIPTION "SNMP Mode: 0 - Disable  1- Enable v1 v2c v3."
		::= { SNMPConfig 1 }

	SNMPReadCommunityName	OBJECT-TYPE
		SYNTAX	DisplayString (SIZE (0..32))
		ACCESS	read-write
		STATUS	mandatory
		DESCRIPTION "SNMP Read CommunityName."
		::= { SNMPConfig 2 }

	SNMPWriteCommunityName	OBJECT-TYPE
		SYNTAX	DisplayString (SIZE (0..32))
		ACCESS	read-write
		STATUS	mandatory
		DESCRIPTION "SNMP Write Community Name." 
		::= { SNMPConfig 3 }

	SNMPV3UserName	OBJECT-TYPE
		SYNTAX	DisplayString (SIZE (0..32))
		ACCESS	read-write
		STATUS	mandatory
		DESCRIPTION "SNMP Version 3 User Name." 
		::= { SNMPConfig 4 }

	SNMPV3UserReadWriteLimit	OBJECT-TYPE
		SYNTAX	INTEGER {
		ReadOnly(0),
		ReadWrite(1)
		} 
		ACCESS	read-write
		STATUS	mandatory
		DESCRIPTION "SNMP V3 User Read Write Limit: 0 - Read Only  1 - Read Write." 
		::= { SNMPConfig 5 }

	SNMPV3UserAuthLevel	OBJECT-TYPE
		SYNTAX	INTEGER {
		NoAuthNopriv(0),
		AuthNoPriv(1),
		AuthPriv(2)
		} 
		ACCESS	read-write
		STATUS	mandatory
		DESCRIPTION "SNMP V3 User Authentication Level: 0 - NoAuthNopriv  1 - AuthNoPriv
		2 - AuthPriv." 
		::= { SNMPConfig 6 }

	SNMPV3AuthPassword	OBJECT-TYPE
		SYNTAX	DisplayString (SIZE (0..32))
		ACCESS	read-write
		STATUS	mandatory
		DESCRIPTION "SNMP V3 Authentication Password." 
		::= { SNMPConfig 7 }

	SNMPV3PrivacyPassword	OBJECT-TYPE
		SYNTAX	DisplayString (SIZE (0..32))
		ACCESS	read-write
		STATUS	mandatory
		DESCRIPTION "SNMP V3 Privacy Passord." 
		::= { SNMPConfig 8 }

	SNMPTrapVersion	OBJECT-TYPE
		SYNTAX	INTEGER {V1Traps(0),V2Traps(1),V3Traps(2),V1V2Traps(3),V1V2V3Traps(4)} 
		ACCESS	read-write
		STATUS	mandatory
		DESCRIPTION "SNMP Trap Version: 0 - V1 Traps  1 - V2 Traps  2 - V3 Traps  
		3 - V1&V2 Traps  4 - V1&V2&V3 Traps." 
		::= { SNMPConfig 9 }

	SNMPAuthTrapStatus	OBJECT-TYPE
		SYNTAX	INTEGER {Disable(0),Enable(1)} 
		ACCESS	read-write
		STATUS	mandatory
		DESCRIPTION "SNMP Authentication Traps Status: 0 - Disable  1 - Enable." 
		::= { SNMPConfig 10 }

	SNMPTrapCommunityName	OBJECT-TYPE
		SYNTAX	DisplayString (SIZE (0..32))
		ACCESS	read-write
		STATUS	mandatory
		DESCRIPTION "SNMP Trap Community Name." 
		::= { SNMPConfig 11 }

	SNMPTrapManageHost	OBJECT-TYPE
		SYNTAX	DisplayString (SIZE (0..32))
		ACCESS	read-write
		STATUS	mandatory
		DESCRIPTION "SNMP Manage Host." 
		::= { SNMPConfig 12 }
 
	SNMPConfigAction	OBJECT-TYPE
		SYNTAX	INTEGER {
		SubmitOrReset(0),
		Submit(1),
		Reset(2)
		} 
		ACCESS	read-write
		STATUS	mandatory
		DESCRIPTION "0-Default no selection.1-Submit,this will update setting immidiately.
		2-Reset,this will cacel all related settings in the sub tree" 
		::= { SNMPConfig 13 }

CarrierConfig	OBJECT IDENTIFIER ::=	{ Carrier 1 }

	Carrier_Config_Carrier_Status	OBJECT-TYPE
		SYNTAX	INTEGER {
		Disable(0),
		Enable(1)
		} 
		ACCESS	read-write
		STATUS	mandatory
		DESCRIPTION "0 - Disable  1- Enable."
		::= { CarrierConfig 1 }

	Carrier_IP_Passthrough	OBJECT-TYPE
		SYNTAX	INTEGER {
		Disable(0),
		Ethernet(1)
		} 
		ACCESS	read-write
		STATUS	mandatory
		DESCRIPTION "Carrier IP Passthrough"
		::= { CarrierConfig 2 }

	Carrier_APN	OBJECT-TYPE
		SYNTAX	DisplayString (SIZE (0..32))
		ACCESS	read-write
		STATUS	mandatory
		DESCRIPTION "Carrier APN" 
		::= { CarrierConfig 3 }


	Carrier_Config_SIM_Pin	OBJECT-TYPE
		SYNTAX	DisplayString (SIZE (0..32))
		ACCESS	read-write
		STATUS	mandatory
		DESCRIPTION "Carrier SIM Card Pin" 
		::= { CarrierConfig 4 }



	Carrier_Config_Technology_Type	OBJECT-TYPE
		SYNTAX	INTEGER {
		All(0),
		3GPP(1),
		3GPP2(2)
		} 
		ACCESS	read-write
		STATUS	mandatory
		DESCRIPTION ""
		::= { CarrierConfig 5 }


	Carrier_Config_Technology_Mode	OBJECT-TYPE
		SYNTAX	DisplayString (SIZE (0..32))
		ACCESS	read-write
		STATUS	mandatory
		DESCRIPTION "Carrier_Config_Technology_Mode" 
		::= { CarrierConfig 6 }

	Carrier_Config_Data_Call_Param	OBJECT-TYPE
		SYNTAX	DisplayString (SIZE (0..32))
		ACCESS	read-write
		STATUS	mandatory
		DESCRIPTION "Carrier_Config_Data_Call_Param" 
		::= { CarrierConfig 7 }

	Carrier_Config_Primary_DNS	OBJECT-TYPE
		SYNTAX	DisplayString (SIZE (0..32))
		ACCESS	read-write
		STATUS	mandatory
		DESCRIPTION "Carrier_Config_Primary_DNS" 
		::= { CarrierConfig 8}


	Carrier_Config_Secondary_DNS	OBJECT-TYPE
		SYNTAX	DisplayString (SIZE (0..32))
		ACCESS	read-write
		STATUS	mandatory
		DESCRIPTION "" 
		::= { CarrierConfig 9 }


	Carrier_Config_Primary_NetBIOS	OBJECT-TYPE
		SYNTAX	DisplayString (SIZE (0..32))
		ACCESS	read-write
		STATUS	mandatory
		DESCRIPTION "" 
		::= { CarrierConfig 10 }

	Carrier_Config_Secondary_NetBIOS	OBJECT-TYPE
		SYNTAX	DisplayString (SIZE (0..32))
		ACCESS	read-write
		STATUS	mandatory
		DESCRIPTION "" 
		::= { CarrierConfig 11 }

	Carrier_Config_IP_Addr	OBJECT-TYPE
		SYNTAX	DisplayString (SIZE (0..32))
		ACCESS	read-write
		STATUS	mandatory
		DESCRIPTION "" 
		::= { CarrierConfig 12 }



	Carrier_Config_Authentication	OBJECT-TYPE
		SYNTAX	INTEGER {
		Device decide(0),
		PAP(1),
		CHAP(2)
		} 
		ACCESS	read-write
		STATUS	mandatory
		DESCRIPTION ""
		::= { CarrierConfig 13 }


	Carrier_Config_User_Name	OBJECT-TYPE
		SYNTAX	DisplayString (SIZE (0..32))
		ACCESS	read-write
		STATUS	mandatory
		DESCRIPTION "" 
		::= { CarrierConfig 14 }

	Carrier_Config_Password 	OBJECT-TYPE
		SYNTAX	DisplayString (SIZE (0..32))
		ACCESS	read-write
		STATUS	mandatory
		DESCRIPTION "" 
		::= { CarrierConfig 15 }

 
	Carrier_Config_ACTION	OBJECT-TYPE
		SYNTAX	INTEGER {
		SubmitOrReset(0),
		Submit(1),
		Reset(2)
		} 
		ACCESS	read-write
		STATUS	mandatory
		DESCRIPTION "0-Default no selection.1-Submit,this will update setting immidiately.
		2-Reset,this will cacel all related settings in the sub tree" 
		::= { CarrierConfig 25 }

CarrierKeepaliveConfig	OBJECT IDENTIFIER ::=	{ Carrier 2 }

	Carrier_Config_Keepalive_Status	OBJECT-TYPE
		SYNTAX	INTEGER {
		Disable(0),
		Enable(1),
		} 
		ACCESS	read-write
		STATUS	mandatory
		DESCRIPTION ""
		::= { CarrierKeepaliveConfig 1 }



	Carrier_Config_Keepalive_Type	OBJECT-TYPE
		SYNTAX	DisplayString (SIZE (0..32))
		ACCESS	read-write
		STATUS	mandatory
		DESCRIPTION "" 
		::= { CarrierKeepaliveConfig 2 }


	Carrier_Config_Keepalive_HostName	OBJECT-TYPE
		SYNTAX	DisplayString (SIZE (0..32))
		ACCESS	read-write
		STATUS	mandatory
		DESCRIPTION "" 
		::= { CarrierKeepaliveConfig 3 }

	Carrier_Config_Keepalive_Interval	OBJECT-TYPE
		SYNTAX	DisplayString (SIZE (0..32))
		ACCESS	read-write
		STATUS	mandatory
		DESCRIPTION "" 
		::= { CarrierKeepaliveConfig 4 }

	Carrier_Config_Keepalive_Count	OBJECT-TYPE
		SYNTAX	DisplayString (SIZE (0..32))
		ACCESS	read-write
		STATUS	mandatory
		DESCRIPTION "" 
		::= { CarrierKeepaliveConfig 5 }

	Carrier_Config_Keepalive_ACTION	OBJECT-TYPE
		SYNTAX	INTEGER {
		SubmitOrReset(0),
		Submit(1),
		Reset(2)
		} 
		ACCESS	read-write
		STATUS	mandatory
		DESCRIPTION "0-Default no selection.1-Submit,this will update setting immidiately.
		2-Reset,this will cacel all related settings in the sub tree" 
		::= { CarrierKeepaliveConfig 25 }


CarrierTrafficWatchdogConfig	OBJECT IDENTIFIER ::=	{ Carrier 3 }

	Carrier_Config_TrafficWatchdog_Status	OBJECT-TYPE
		SYNTAX	INTEGER {
		Disable(0),
		Enable(1),
		} 
		ACCESS	read-write
		STATUS	mandatory
		DESCRIPTION ""
		::= { CarrierTrafficWatchdogConfig 1 }



	Carrier_Config_TrafficWatchdog_Interval	OBJECT-TYPE
		SYNTAX	DisplayString (SIZE (0..32))
		ACCESS	read-write
		STATUS	mandatory
		DESCRIPTION "" 
		::= { CarrierTrafficWatchdogConfig 2 }


	Carrier_Config_TrafficWatchdog_RebootTime	OBJECT-TYPE
		SYNTAX	DisplayString (SIZE (0..32))
		ACCESS	read-write
		STATUS	mandatory
		DESCRIPTION "" 
		::= { CarrierTrafficWatchdogConfig 3 }


	Carrier_Config_TrafficWatchdog_ACTION	OBJECT-TYPE
		SYNTAX	INTEGER {
		SubmitOrReset(0),
		Submit(1),
		Reset(2)
		} 
		ACCESS	read-write
		STATUS	mandatory
		DESCRIPTION "0-Default no selection.1-Submit,this will update setting immidiately.
		2-Reset,this will cacel all related settings in the sub tree" 
		::= { CarrierTrafficWatchdogConfig 25 }


CarrierDDNSConfig	OBJECT IDENTIFIER ::=	{ Carrier 4 }

	Carrier_Config_DDNS_Status	OBJECT-TYPE
		SYNTAX	INTEGER {
		Disable(0),
		Enable(1),
		} 
		ACCESS	read-write
		STATUS	mandatory
		DESCRIPTION ""
		::= { CarrierDDNSConfig 1 }



	Carrier_Config_DDNS_Service	OBJECT-TYPE
		SYNTAX	DisplayString (SIZE (0..32))
		ACCESS	read-write
		STATUS	mandatory
		DESCRIPTION "" 
		::= { CarrierDDNSConfig 2 }


	Carrier_Config_DDNS_UserName	OBJECT-TYPE
		SYNTAX	DisplayString (SIZE (0..32))
		ACCESS	read-write
		STATUS	mandatory
		DESCRIPTION "" 
		::= { CarrierDDNSConfig 3 }

	Carrier_Config_DDNS_Password	OBJECT-TYPE
		SYNTAX	DisplayString (SIZE (0..32))
		ACCESS	read-write
		STATUS	mandatory
		DESCRIPTION "" 
		::= { CarrierDDNSConfig 4 }

	Carrier_Config_DDNS_Host	OBJECT-TYPE
		SYNTAX	DisplayString (SIZE (0..32))
		ACCESS	read-write
		STATUS	mandatory
		DESCRIPTION "" 
		::= { CarrierDDNSConfig 5 }

	Carrier_Config_DDNS_ACTION	OBJECT-TYPE
		SYNTAX	INTEGER {
		SubmitOrReset(0),
		Submit(1),
		Reset(2)
		} 
		ACCESS	read-write
		STATUS	mandatory
		DESCRIPTION "0-Default no selection.1-Submit,this will update setting immidiately.
		2-Reset,this will cacel all related settings in the sub tree" 
		::= { CarrierDDNSConfig 25 }

-- Wifi  parameter group 
	WifiConfig	OBJECT IDENTIFIER ::=	{ RadioConfig 1 }
		-- WifiConfig parameter group
	
	Wifi_Config_Operation_Mode	OBJECT-TYPE
		SYNTAX	INTEGER {
		AccessPoint(0),
		Station(1),
		Mesh(2),
		Repeater(3),
		} 
		ACCESS	read-write
		STATUS	mandatory
		DESCRIPTION "0-Access Point, 1-Station,2-Mesh,3-Repeater" 
		::= { WifiConfig 1 }
		
	WifiNetworkMode	OBJECT-TYPE
		SYNTAX	INTEGER {
		80211a(0),
		80211bg(1),
		80211g(2)
		} 
		ACCESS	read-write
		STATUS	mandatory
		DESCRIPTION "0-802.11a, 1-802.11bg, 3-802.11g" 
		::= { WifiConfig 2 }
 	
	WifiNetworkName	OBJECT-TYPE
		SYNTAX	DisplayString (SIZE (0..32))
		ACCESS	read-write
		STATUS	mandatory
		DESCRIPTION "Radio Network Name"
		::= { WifiConfig 3 }
	
	WifiNetworkBroacast	OBJECT-TYPE
		SYNTAX	INTEGER {
		broadcast(0),
		hidden(1)
		} 
		ACCESS	read-write
		STATUS	mandatory
		DESCRIPTION "0-Broadcast, 1-Hidden" 
		::= { WifiConfig 5 }
	
--Radio Tx Rate should change according to different product,this is 802.11g   

	WifiTxPower	OBJECT-TYPE
		SYNTAX	INTEGER {
		20dBm(20), 
		21dBm(21), 
		22dBm(22), 
		23dBm(23), 
		24dBm(24), 
		25dBm(25), 
		26dBm(26), 
		27dBm(27), 
		28dBm(28) 
		} 
		ACCESS	read-write
		STATUS	mandatory
		DESCRIPTION "20-20dBm, 21-21dBm" 
		::= { WifiConfig 6 }

--Radio Channel should change according to different product,this is 802.11g   

	WifiChannelbandwidth	OBJECT-TYPE
		SYNTAX	INTEGER {                
		NormalRate(0), 
		QuarterRate(1), 
		HalfRate (2), 
		TurboRate(3), 
		} 
		ACCESS	read-write
		STATUS	mandatory
		DESCRIPTION "0-Normal,1-Quarter,2-Half,3-Turbo" 
		::= { WifiConfig 7 }
 
 
	WifiChannel	OBJECT-TYPE
		SYNTAX	DisplayString (SIZE (0..32))
		ACCESS	read-write
		STATUS	mandatory
		DESCRIPTION "Channel"
		::= { WifiConfig 8 }

--Radio Tx Rate should change according to different product,this is 802.11g   

	WifiTxRate	OBJECT-TYPE
		SYNTAX	DisplayString (SIZE (0..32))
		ACCESS	read-write
		STATUS	mandatory
		DESCRIPTION "Tx Rate"
		::= { WifiConfig 10 }

  	WifiBasicConfigAction	OBJECT-TYPE
		SYNTAX	INTEGER {
		SubmitOrReset(0),
		Submit(1),
		Reset(2)
		} 
		ACCESS	read-write
		STATUS	mandatory
		DESCRIPTION "0-Default no selection.1-Submit,this will update setting immidiately.
		2-Reset,this will cacel all related settings in the sub tree" 
		::= { WifiConfig 11 }
  
	WifiFragmentationThreshold	OBJECT-TYPE
		SYNTAX	DisplayString (SIZE (0..32))
		ACCESS	read-write
		STATUS	mandatory
		DESCRIPTION "Fragmentation Threshold"
		::= { WifiConfig 17 }
	
	WifiRTSThreshold	OBJECT-TYPE
		SYNTAX	DisplayString (SIZE (0..32))
		ACCESS	read-write
		STATUS	mandatory
		DESCRIPTION "RTS Threshold"
		::= { WifiConfig 18 }

	WifiDistance	OBJECT-TYPE
		SYNTAX	DisplayString (SIZE (0..32))
		ACCESS	read-write
		STATUS	mandatory
		DESCRIPTION "Distance"
		::= { WifiConfig 12 }

	WifiRadioWds	OBJECT-TYPE
		SYNTAX	INTEGER {
		WdsDisabled(0),
		WdsEnable(1)
		} 
		ACCESS	read-write
		STATUS	mandatory
		DESCRIPTION "0-Disable, 1-Enable" 
		::= { WifiConfig 13 }

	 WifiEncryptionType		OBJECT-TYPE
		SYNTAX	INTEGER {
		Disabled(0),
		WEP(1),
		WPA(2),
		WPA2(3),
		WPAWPA2(4),
		WPARADIUS(5),
		WPA2RADIUS(6)
		} 
		ACCESS	read-write
		STATUS	mandatory
		DESCRIPTION "0-Disable, 1-WEP, 2-WPA, 3-WPA2, 4-WPA+WPA2, 5-WPARADIUS, 6-WPA2RADIUS" 
		::= { WifiConfig 14 }

	WifiKey	OBJECT-TYPE
		SYNTAX	DisplayString (SIZE (0..32))
		ACCESS	read-write
		STATUS	mandatory
		DESCRIPTION "Key"
		::= { WifiConfig 19 }
				             
	WifiKey1	OBJECT-TYPE
		SYNTAX	DisplayString (SIZE (0..32))
		ACCESS	read-write
		STATUS	mandatory
		DESCRIPTION "Key1"
		::= { WifiConfig 20 }
	WifiKey2	OBJECT-TYPE
		SYNTAX	DisplayString (SIZE (0..32))
		ACCESS	read-write
		STATUS	mandatory
		DESCRIPTION "Key2"
		::= { WifiConfig 21 }
	WifiKey3	OBJECT-TYPE
		SYNTAX	DisplayString (SIZE (0..32))
		ACCESS	read-write
		STATUS	mandatory
		DESCRIPTION "Key3"
		::= { WifiConfig 22 }

	WifiKey4	OBJECT-TYPE
		SYNTAX	DisplayString (SIZE (0..32))
		ACCESS	read-write
		STATUS	mandatory
		DESCRIPTION "Key4"
		::= { WifiConfig 23 }
				             
				             
  	WifiConfigAction	OBJECT-TYPE
		SYNTAX	INTEGER {
		SubmitOrReset(0),
		Submit(1),
		Reset(2)
		} 
		ACCESS	read-write
		STATUS	mandatory
		DESCRIPTION "0-Default no selection.1-Submit,this will update setting immidiately.
		2-Reset,this will cacel all related settings in the sub tree" 
		::= { WifiConfig 24 }


-- COM1 parameter group

	COM1_Port_Status	OBJECT-TYPE
		SYNTAX	INTEGER {	Disable(0),	Enable(1)} 
		ACCESS	read-write
		STATUS	mandatory
		DESCRIPTION "COM1 Port Status: 0 - Disable  1 - Enable" 
		::= { COM1Config 1 }  

	COM1_Chanel_Mode	OBJECT-TYPE
		SYNTAX	INTEGER {RS232(0),RS485(1),RS422(2)} 
		ACCESS	read-write
		STATUS	mandatory
		DESCRIPTION "COM1 Channel Mode: A - RS232  B - RS485  C - RS422" 
		::= { COM1Config 2 }  

	COM1_Data_Baud_Rate	OBJECT-TYPE
		SYNTAX	INTEGER {B300(0),B600(1),B1200(2),B2400(3), B3600(4),B4800(5),
		B7200(6),B9600(7),B14400(8),B19200(9),B28800(10),B38400(11),B57600(12),
		B115200(13),B230400(14),B460800(15),B921600(16)} 
		ACCESS	read-write
		STATUS	mandatory
		DESCRIPTION "COM1 Data Baud Rate: 0 - 300  1 - 600  2 - 1200
		3 - 2400  4 - 3600  5 - 4800  6 - 7200  7 - 9600  8 - 14400  9 - 19200
		10 - 28800  11 - 38400  12 - 57600  13 - 115200  14 - 230400 15-460800,16-961600"
		::= { COM1Config 3 }  

	COM1_Data_Format	OBJECT-TYPE
		SYNTAX	INTEGER {_8N1(0),_8N2(1),_8E1(2),_8O1(3), _7N1(4),
		_7N2(5),_7E1(6),_7O1(7),_7E2(8), _7O2(9)} 
		ACCESS	read-write
		STATUS	mandatory
		DESCRIPTION "COM1 Data Format: 0 - 8N1  1 - 8N2  2 - 8E1  3 - 8O1
		4 - 7N1  5 - 7N2  6 - 7E1  7 - 7O1  8 - 7E2  9 - 7O2 " 
		::= { COM1Config 4 }  

	COM1_Flow_Control	OBJECT-TYPE
		SYNTAX	INTEGER { None(0),Hardware(1),CTSFraming(2)} 	 
		ACCESS	read-write
		STATUS	mandatory
		DESCRIPTION "COM1 Flow Control: 0 - None  1 - Hardware 2- CTS Framing" 
		::= { COM1Config 5 }  

	COM1_PreData_Delay	OBJECT-TYPE
		SYNTAX	DisplayString (SIZE (0..32))	 
		ACCESS	read-write
		STATUS	mandatory
		DESCRIPTION "COM1 Pre-frame Delay." 
		::= { COM1Config 6 }  
	
	COM1_PostData_Delay	OBJECT-TYPE
		SYNTAX	DisplayString (SIZE (0..32))	 
		ACCESS	read-write
		STATUS	mandatory
		DESCRIPTION "COM1 Post-frame Delay." 
		::= { COM1Config 7 }  
		
	COM1_Data_Mode	OBJECT-TYPE
		SYNTAX	INTEGER {Modbus(0),Transparent(1)} 
		ACCESS	read-write
		STATUS	mandatory
		DESCRIPTION "COM1 Data Mode: 0 - Modbus  1 - Transparent." 
		::= { COM1Config 8 }  

	COM1_Character_Timeout	OBJECT-TYPE
		SYNTAX	DisplayString (SIZE (0..32))	 
		ACCESS	read-write
		STATUS	mandatory
		DESCRIPTION "COM1 Character Timeout." 
		::= { COM1Config 9 }  

	COM1_Maximum_Packet_Size	OBJECT-TYPE
		SYNTAX	DisplayString (SIZE (0..32))	 
		ACCESS	read-write
		STATUS	mandatory
		DESCRIPTION "COM1 Maxmum Packet Size." 
		::= { COM1Config 10 }  
     
	COM1_Priority	OBJECT-TYPE
		SYNTAX	INTEGER {
		Normal(0),
		Medium(1),
		High(2),
		} 
		ACCESS	read-write
		STATUS	mandatory
		DESCRIPTION "COM1 Data Format: 0 - Normal  1 - Medium  2 - High " 
		::= { COM1Config 21 }  
 	
	COM1_No_Connection_Data_Intake	OBJECT-TYPE
		SYNTAX	INTEGER {
		Disable(0),
		Enable(1),
		} 
		ACCESS	read-write
		STATUS	mandatory
		DESCRIPTION "COM1 No Connection Data Intake: 0 - Disable  1 - Enable " 
		::= { COM1Config 22 }  

 	COM1_Modbus_Status	OBJECT-TYPE
		SYNTAX	INTEGER {
		Disable(0),
		Enable(1),
		} 
		ACCESS	read-write
		STATUS	mandatory
		DESCRIPTION "COM1 Modbus Status: 0 - Disable  1 - Enable " 
		::= { COM1Config 23 }     

	COM1_Modbus_Protection_Status	OBJECT-TYPE
		SYNTAX	INTEGER {
		Disable(0),
		Enable(1),
		} 
		ACCESS	read-write
		STATUS	mandatory
		DESCRIPTION "COM1 Modbus Protection Status: 0 - Disable  1 - Enable " 
		::= { COM1Config 24 }     

	COM1_Modbus_Protection_Key	OBJECT-TYPE
		SYNTAX	DisplayString (SIZE (0..32))	 
		ACCESS	read-write
		STATUS	mandatory
		DESCRIPTION "COM1 Modbus Protection Key" 
		::= { COM1Config 25 } 
       
	COM1_IP_Protocol	OBJECT-TYPE
		SYNTAX	INTEGER {
		TCPClient(0),
		TCPServer(1),
		TCPClientServer(2),
		UDPPointtoPoint(3),
		UDPPointtoMultiPoint_as_point(4),
		UDPPointtoMultiPoint_as_Multipoint(5),
		UDPMultiPoint_to_Multipoint(6),
		smtp(7),
		} 
		ACCESS	read-write
		STATUS	mandatory
		DESCRIPTION "COM1 IP Protocol: 0 - TCP Client  1 - TCP Server  2 - TCP Client/Server
		3 - UDP Point to Point  4 - UDP Point to MultiPoint(as point) 
		5 - UDP Point to MultiPoint(as Multipoint).6-UDP MultiPoint to Multipoint
		7 - smtp" 
		::= { COM1Config 11 } 

	COM1AsTCPClientConfig	OBJECT IDENTIFIER ::=	{ COM1Config 12}

		-- COM1TCPClientConfig Command group

	COM1_T_Client_Server_Addr	OBJECT-TYPE
		SYNTAX	DisplayString (SIZE (0..32))	 
		ACCESS	read-write
		STATUS	mandatory
		DESCRIPTION "COM1 as TCP Client Remote Server Ip Address." 
		::= { COM1AsTCPClientConfig 1 }  

	COM1_T_Client_Server_Port	OBJECT-TYPE
		SYNTAX	DisplayString (SIZE (0..32))	 
		ACCESS	read-write
		STATUS	mandatory
		DESCRIPTION "COM1 as TCP Client Remote Server Listen Port." 
		::= { COM1AsTCPClientConfig 2 }  

	COM1_T_Client_Timeout	OBJECT-TYPE
		SYNTAX	DisplayString (SIZE (0..32))	 
		ACCESS	read-write
		STATUS	mandatory
		DESCRIPTION "COM1 as TCP Client Connection Timeout." 
		::= { COM1AsTCPClientConfig 3 }  

	COM1AsTCPServerConfig	OBJECT IDENTIFIER ::=	{ COM1Config 13 }

		-- COM1TCPServerConfig Command group

 	COM1_T_Server_Listen_Port	OBJECT-TYPE
		SYNTAX	DisplayString (SIZE (0..32))	 
		ACCESS	read-write
		STATUS	mandatory
		DESCRIPTION "COM1 as TCP Server Listen Port." 
		::= { COM1AsTCPServerConfig 1 }  

	COM1_T_Server_Timeout	OBJECT-TYPE
		SYNTAX	DisplayString (SIZE (0..32))	 
		ACCESS	read-write
		STATUS	mandatory
		DESCRIPTION "COM1 as TCP Server  Remote Client Connection Timeout." 
		::= { COM1AsTCPServerConfig 2 }  

	 COM1AsUDPPointToPointConfig		OBJECT IDENTIFIER ::=	{ COM1Config 15 }

		-- COM1UDPPointToPointConfig Command group

	COM1_U_PtoP_Remote_Addr	OBJECT-TYPE
		SYNTAX	DisplayString (SIZE (0..32))	 
		ACCESS	read-write
		STATUS	mandatory
		DESCRIPTION "COM1 as UDP Point to Point Remote Ip Address." 
		::= { COM1AsUDPPointToPointConfig 1 }  

	COM1_U_PtoP_Remote_Port	OBJECT-TYPE
		SYNTAX	DisplayString (SIZE (0..32))	 
		ACCESS	read-write
		STATUS	mandatory
		DESCRIPTION "COM1 as UDP Point to Point Remote Server Listen Port." 
		::= { COM1AsUDPPointToPointConfig 2 }

	COM1_U_PtoP_Listen_Port	OBJECT-TYPE
		SYNTAX	DisplayString (SIZE (0..32)) 
		ACCESS	read-write
		STATUS	mandatory
		DESCRIPTION "COM1 as UDP Point to Point Connection Local Listen Port." 
		::= { COM1AsUDPPointToPointConfig 3 }

	COM1AsUDPPointToMultiPointasPointConfig	OBJECT IDENTIFIER ::=	{ COM1Config 16 }

		-- COM1UDPPointToMultiPointasPointConfig Command group

	COM1_UM_P_Multicast_Addr	OBJECT-TYPE
		SYNTAX	DisplayString (SIZE (0..32)) 
		ACCESS	read-write
		STATUS	mandatory
		DESCRIPTION "Multicast Address." 
		::= { COM1AsUDPPointToMultiPointasPointConfig 1 }

	COM1_UM_P_Multicast_Port	OBJECT-TYPE
		SYNTAX	DisplayString (SIZE (0..32)) 
		ACCESS	read-write
		STATUS	mandatory
		DESCRIPTION "Multicast Port." 
		::= { COM1AsUDPPointToMultiPointasPointConfig 2 }  

	COM1_UM_P_Listen_Port	OBJECT-TYPE
		SYNTAX	DisplayString (SIZE (0..32))
		ACCESS	read-write
		STATUS	mandatory
		DESCRIPTION "Local Listen Port." 
		::= { COM1AsUDPPointToMultiPointasPointConfig 3 }

	COM1_UM_P_TTL 	OBJECT-TYPE
		SYNTAX	DisplayString (SIZE (0..32))
		ACCESS	read-write
		STATUS	mandatory
		DESCRIPTION "Multicast TTL Value." 
		::= { COM1AsUDPPointToMultiPointasPointConfig 4 }

	COM1AsUDPPointToMultiPointasMultiPointConfig	OBJECT IDENTIFIER ::=	{ COM1Config 17 }
		-- COM1UDPPointToMultiPointasMultiPointConfig Command group

	COM1_UM_M_Remote_Addr	OBJECT-TYPE
		SYNTAX	DisplayString (SIZE (0..32))
		ACCESS	read-write
		STATUS	mandatory
		DESCRIPTION "Remote IP Address."
		::= { COM1AsUDPPointToMultiPointasMultiPointConfig 1 }

	COM1_UM_M_Remote_Port	OBJECT-TYPE
		SYNTAX	DisplayString (SIZE (0..32))
		ACCESS	read-write
		STATUS	mandatory
		DESCRIPTION "Remote Port." 
		::= { COM1AsUDPPointToMultiPointasMultiPointConfig 2 }  

	COM1_UM_M_Multicast_Addr	OBJECT-TYPE
		SYNTAX	DisplayString (SIZE (0..32))
		ACCESS	read-write
		STATUS	mandatory
		DESCRIPTION "Multicast Address." 
		::= { COM1AsUDPPointToMultiPointasMultiPointConfig 3 }  

	COM1_UM_M_Multicast_Port 	OBJECT-TYPE
		SYNTAX	DisplayString (SIZE (0..32))	 
		ACCESS	read-write
		STATUS	mandatory
		DESCRIPTION "Multicast Port." 
		::= { COM1AsUDPPointToMultiPointasMultiPointConfig 4 }

	COM1AsUDPMultiPointToMultiPointConfig	OBJECT IDENTIFIER ::=	{ COM1Config 18 }
		-- COM1AsUDPMultiPointToMultiPointConfig Command group  
	
	COM1_UMtoM_Multicast_IP	OBJECT-TYPE
		SYNTAX	DisplayString (SIZE (0..32))
		ACCESS	read-write
		STATUS	mandatory
		DESCRIPTION "Multicast Port." 
		::= { COM1AsUDPMultiPointToMultiPointConfig 1 }

	COM1_UMtoM_Multicast_Port	OBJECT-TYPE
		SYNTAX	DisplayString (SIZE (0..32))
		ACCESS	read-write
		STATUS	mandatory
		DESCRIPTION "Local Listen Port." 
		::= { COM1AsUDPMultiPointToMultiPointConfig 2 }

	COM1_UMtoM_Multicast_TTL 	OBJECT-TYPE
		SYNTAX	DisplayString (SIZE (0..32))
		ACCESS	read-write
		STATUS	mandatory
		DESCRIPTION "Multicast TTL Value." 
		::= { COM1AsUDPMultiPointToMultiPointConfig 3 }

	COM1_UMtoM_Listen_Multicast_IP	OBJECT-TYPE
		SYNTAX	DisplayString (SIZE (0..32))
		ACCESS	read-write
		STATUS	mandatory
		DESCRIPTION "Multicast Address." 
		::= { COM1AsUDPMultiPointToMultiPointConfig 4 }

	COM1_UMtoM_Listen_Multicast_Port 	OBJECT-TYPE
		SYNTAX	DisplayString (SIZE (0..32))
		ACCESS	read-write
		STATUS	mandatory
		DESCRIPTION "Multicast Port." 
		::= { COM1AsUDPMultiPointToMultiPointConfig 5 }

	COM1AsSMTPClientConfig	OBJECT IDENTIFIER ::=	{ COM1Config 19 }          
	-- COM1AsSMTPClientConfig Command group
	
	COM1_SMTP_Mail_Subject 	OBJECT-TYPE
		SYNTAX	DisplayString (SIZE (0..32))
		ACCESS	read-write
		STATUS	mandatory
		DESCRIPTION "Multicast Port." 
		::= { COM1AsSMTPClientConfig 1 }  
 	 
	COM1_SMTP_Mail_Server 	OBJECT-TYPE
		SYNTAX	DisplayString (SIZE (0..32))
		ACCESS	read-write
		STATUS	mandatory
		DESCRIPTION "Multicast Port." 
		::= { COM1AsSMTPClientConfig 2 }  
		
	COM1_SMTP_Mail_Recipient	OBJECT-TYPE
		SYNTAX	DisplayString (SIZE (0..32))
		ACCESS	read-write
		STATUS	mandatory
		DESCRIPTION "Multicast Port."
		::= { COM1AsSMTPClientConfig 3 }
 	 
	COM1_SMTP_Mail_MaxSize 	OBJECT-TYPE
		SYNTAX	DisplayString (SIZE (0..32))	 
		ACCESS	read-write
		STATUS	mandatory
		DESCRIPTION "Multicast Port."
		::= { COM1AsSMTPClientConfig 4 }  
 	 
	COM1_SMTP_Mail_Timeout 	OBJECT-TYPE
		SYNTAX	DisplayString (SIZE (0..32))	 
		ACCESS	read-write
		STATUS	mandatory
		DESCRIPTION "Multicast Port."
		::= { COM1AsSMTPClientConfig 5 }  
 	 
	COM1_SMTP_Mail_TransferMode	OBJECT-TYPE
		 SYNTAX	INTEGER {
		Text(0),
		Attached(1),
		Hex(2),
		} 
		ACCESS	read-write
		STATUS	mandatory
		DESCRIPTION "Multicast Port."
		::= { COM1AsSMTPClientConfig 6 }  

	 COM1_Config_ACTION	OBJECT-TYPE
		SYNTAX	INTEGER {
		SubmitOrReset(0),
		Submit(1),
		Reset(2),
		} 
		ACCESS	read-write
		STATUS	mandatory
		DESCRIPTION "0-Default no selection.1-Submit,this will update setting immidiately.
		2-Reset,this will cacel all related settings in the sub tree" 
		::= { COM1Config 20}



-- IOPorts Command group


 	Input1	OBJECT-TYPE
		SYNTAX	INTEGER {
		Open(0),
		Close(1),
		} 
		ACCESS	read-write
		STATUS	mandatory
		DESCRIPTION "Input 1 Status: 0 - open  1 - close " 
		::= { IOPort 1 }    



 	Input2	OBJECT-TYPE
		SYNTAX	INTEGER {
		Open(0),
		Close(1),
		} 
		ACCESS	read-write
		STATUS	mandatory
		DESCRIPTION "Input 2 Status: 0 - open  1 - close " 
		::= { IOPort 2 }    

 	Input3	OBJECT-TYPE
		SYNTAX	INTEGER {
		Open(0),
		Close(1),
		} 
		ACCESS	read-write
		STATUS	mandatory
		DESCRIPTION "Input 3 Status: 0 - open  1 - close " 
		::= { IOPort 3 }    


 	Input4	OBJECT-TYPE
		SYNTAX	INTEGER {
		Open(0),
		Close(1),
		} 
		ACCESS	read-write
		STATUS	mandatory
		DESCRIPTION "Input 4 Status: 0 - open  1 - close " 
		::= { IOPort 4 }    

 	Output1	OBJECT-TYPE
		SYNTAX	INTEGER {
		Open(0),
		Close(1),
		} 
		ACCESS	read-write
		STATUS	mandatory
		DESCRIPTION "Output 1 Status: 0 - open  1 - close " 
		::= { IOPort 1 }    



 	Output2	OBJECT-TYPE
		SYNTAX	INTEGER {
		Open(0),
		Close(1),
		} 
		ACCESS	read-write
		STATUS	mandatory
		DESCRIPTION "Output 2 Status: 0 - open  1 - close " 
		::= { IOPort 2 }    

 	Output3	OBJECT-TYPE
		SYNTAX	INTEGER {
		Open(0),
		Close(1),
		} 
		ACCESS	read-write
		STATUS	mandatory
		DESCRIPTION "Output 3 Status: 0 - open  1 - close " 
		::= { IOPort 3 }    


 	Output4	OBJECT-TYPE
		SYNTAX	INTEGER {
		Open(0),
		Close(1),
		} 
		ACCESS	read-write
		STATUS	mandatory
		DESCRIPTION "Output 4 Status: 0 - open  1 - close " 
		::= { IOPort 4 }    




-- SystemInformation Command group

	 Ethernet0Information	OBJECT IDENTIFIER ::=	{ SystemInformation 1 }
	 Ethernet1Information	OBJECT IDENTIFIER ::=	{ SystemInformation 2 }
	 RadioInformation	OBJECT IDENTIFIER ::=	{ SystemInformation 3 }
	 Com1Information	OBJECT IDENTIFIER ::=	{ SystemInformation 4 }

	-- Ethernet0Information group

	Ethernet0ReceivedBytes	OBJECT-TYPE
		SYNTAX	INTEGER  
		ACCESS	read-only
		STATUS	mandatory
		DESCRIPTION "Ethernet0 Received bytes"
		::= { Ethernet0Information 1 }

	Ethernet0ReceivedPackets	 OBJECT-TYPE
		SYNTAX	INTEGER  
		ACCESS	read-only
		STATUS	mandatory
		DESCRIPTION "Ethernet0 Received packets"
		::= { Ethernet0Information 2 }

	Ethernet0TransmittedBytes	OBJECT-TYPE
		SYNTAX	INTEGER  
		ACCESS	read-only
		STATUS	mandatory
		DESCRIPTION "Ethernet0 Transmitted bytes"
		::= { Ethernet0Information 9 }

	Ethernet0TransmittedPackets	OBJECT-TYPE
		SYNTAX	INTEGER  
		ACCESS	read-only
		STATUS	mandatory
		DESCRIPTION "Ethernet0 Transmitted packets"
		::= { Ethernet0Information 10 }

      -- Ethernet1Information group

	Ethernet1ReceivedBytes	OBJECT-TYPE
		SYNTAX	INTEGER 
		ACCESS	read-only
		STATUS	mandatory
		DESCRIPTION "Ethernet1 Received bytes"
		::= { Ethernet1Information 1 }

	Ethernet1ReceivedPackets	 OBJECT-TYPE
		SYNTAX	INTEGER 
		ACCESS	read-only
		STATUS	mandatory
		DESCRIPTION "Ethernet1 Received packets"
		::= { Ethernet1Information 2 }
	Ethernet1TransmittedBytes	OBJECT-TYPE
		SYNTAX	INTEGER 
		ACCESS	read-only
		STATUS	mandatory
		DESCRIPTION "Ethernet1 Transmitted bytes"
		::= { Ethernet1Information 9 }

	Ethernet1TransmittedPackets	OBJECT-TYPE
		SYNTAX	INTEGER 
		ACCESS	read-only
		STATUS	mandatory
		DESCRIPTION "Ethernet1 Transmitted packets"
		::= { Ethernet1Information 10 }

-- WifiInformation group

	WifiReceivedBytes	OBJECT-TYPE
		SYNTAX	INTEGER 
		ACCESS	read-only
		STATUS	mandatory
		DESCRIPTION "Radio Received bytes"
		::= { RadioInformation 1 }

	WifiReceivedPackets	OBJECT-TYPE
		SYNTAX	INTEGER 
		ACCESS	read-only
		STATUS	mandatory
		DESCRIPTION "Radio Received packets"
		::= { RadioInformation 2 }

	WifiTransmittedBytes	OBJECT-TYPE
		SYNTAX	INTEGER 
		ACCESS	read-only
		STATUS	mandatory
		DESCRIPTION "Radio Transmitted bytes"
		::= { RadioInformation 3 }

	WifiTransmittedPackets	OBJECT-TYPE
		SYNTAX	INTEGER 
		ACCESS	read-only
		STATUS	mandatory
		DESCRIPTION "Radio Transmitted packets"
		::= { RadioInformation 4 }

	-- Com1Information group

 	Com1ReceivedBytes	OBJECT-TYPE
		SYNTAX	INTEGER 
		ACCESS	read-only
		STATUS	mandatory
		DESCRIPTION "Com1 Received bytes"
		::= { Com1Information 1 }

	Com1ReceivedPackets	OBJECT-TYPE
		SYNTAX	INTEGER 
		ACCESS	read-only
		STATUS	mandatory
		DESCRIPTION "Com1 Received packets"
		::= { Com1Information 2 }

	Com1ReceivedErrors	OBJECT-TYPE
		SYNTAX	INTEGER 
		ACCESS	read-only
		STATUS	mandatory
		DESCRIPTION "Com1 Received errors"
		::= { Com1Information 3 }

	Com1ReceivedDroppedPackets	OBJECT-TYPE
		SYNTAX	INTEGER 
		ACCESS	read-only
		STATUS	mandatory
		DESCRIPTION "Com1 Received droped packets"
		::= { Com1Information 4 }	 

	Com1ReceivedFifo	OBJECT-TYPE
		SYNTAX	INTEGER 
		ACCESS	read-only
		STATUS	mandatory
		DESCRIPTION "Com1 Received fifo"
		::= { Com1Information 5 }

	Com1ReceivedFrame	OBJECT-TYPE
		SYNTAX	INTEGER 
		ACCESS	read-only
		STATUS	mandatory
		DESCRIPTION "Com1 Received frame"
		::= { Com1Information 6 }

	Com1Compressed	OBJECT-TYPE
		SYNTAX	INTEGER 
		ACCESS	read-only
		STATUS	mandatory
		DESCRIPTION "Com1 Compressed"
		::= { Com1Information 7 }

	Com1ReceivedMulticast	OBJECT-TYPE
		SYNTAX	INTEGER 
		ACCESS	read-only
		STATUS	mandatory
		DESCRIPTION "Com1 Received multicast"
		::= { Com1Information 8 }

	Com1TransmittedBytes	OBJECT-TYPE
		SYNTAX	INTEGER 
		ACCESS	read-only
		STATUS	mandatory
		DESCRIPTION "Com1 Transmitted bytes"
		::= { Com1Information 9 }

 	Com1TransmittedPackets	OBJECT-TYPE
		SYNTAX	INTEGER 
		ACCESS	read-only
		STATUS	mandatory
		DESCRIPTION "Com1 Transmitted packets"
		::= { Com1Information 10 }
 
	Com1TransmittedErrors	OBJECT-TYPE
		SYNTAX	INTEGER 
		ACCESS	read-only
		STATUS	mandatory
		DESCRIPTION "Com1 Transmitted errors"
		::= { Com1Information 11 }

	Com1TransmittedDropedPackets OBJECT-TYPE
		SYNTAX	INTEGER 
		ACCESS	read-only
		STATUS	mandatory
		DESCRIPTION "Com1 Transmitted droped packets"
		::= { Com1Information 12 }
 
	Com1TransmittedFifo	OBJECT-TYPE
		SYNTAX	INTEGER 
		ACCESS	read-only
		STATUS	mandatory
		DESCRIPTION "Com1 Transmitted fifo"
		::= { Com1Information 13 }
 
	Com1TransmittedCollisions	OBJECT-TYPE
		SYNTAX	INTEGER 
		ACCESS	read-only
		STATUS	mandatory
		DESCRIPTION "Com1 Transmitted collisions"
		::= { Com1Information 14 }
 
	Com1TransmittedCarrier	OBJECT-TYPE
		SYNTAX	INTEGER 
		ACCESS	read-only
		STATUS	mandatory
		DESCRIPTION "Com1 Transmitted carrier"
		::= { Com1Information 15 }

	Com1TransmittedCompress	OBJECT-TYPE
		SYNTAX	INTEGER 
		ACCESS	read-only
		STATUS	mandatory
		DESCRIPTION "Com1 Transmitted compress"
		::= { Com1Information 16 }

	-- Tool_ResetSystem group

	ToolRebootSystem	OBJECT IDENTIFIER ::=	{ SystemTools 2 }

	Tool_Reset_SystemAction	OBJECT-TYPE
		SYNTAX	INTEGER {
		SubmitOrReset(0),
		Submit(1),
		Reset(2)
		} 
		ACCESS	read-write
		STATUS	mandatory
		DESCRIPTION "0-Default no selection.1-Submit,this will update setting immidiately.
		2-Reset,this will cacel all related settings in the sub tree" 
		::= { ToolRebootSystem 1 }

-- Misc_Config Command group, this group is the misc staff required by different customers.

	WifiAssociationInfo	OBJECT-TYPE
		SYNTAX	DisplayString 
		ACCESS	read-only
		STATUS	mandatory
		DESCRIPTION "Radio Association Information."
		::= { Misc 1 }

END
